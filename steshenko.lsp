(setq scale (getint "\nSet scale: "))
(setq extrude_scale (getint "\nSet extrude scale: "))

;'П'
(setq p1 (list (* 0 scale) (* 0 scale)))
(setq p2 (list (* 0 scale) (* 5 scale)))
(setq p3 (list (* 3 scale) (* 5 scale)))
(setq p4 (list (* 3 scale) (* 0 scale)))
(setq p5 (list (* 2 scale) (* 0 scale)))
(setq p6 (list (* 2 scale) (* 4 scale)))
(setq p7 (list (* 1 scale) (* 4 scale)))
(setq p8 (list (* 1 scale) (* 0 scale)))
(setq p9 (list (* 0 scale) (* 0 scale)))
(command "PLINE" p1 p2 p3 p4 p5 p6 p7 p8 p9 "")
(command "EXTRUDE" (entlast) "" extrude_scale "")

;'Р'
(setq p1 (list (* (+ 4 0) scale) (* 0 scale)))
(setq p2 (list (* (+ 4 0) scale) (* 5 scale)))
(setq p3 (list (* (+ 4 3) scale) (* 5 scale)))
(setq p4 (list (* (+ 4 3) scale) (* 2 scale)))
(setq p5 (list (* (+ 4 1) scale) (* 2 scale)))
(setq p6 (list (* (+ 4 1) scale) (* 0 scale)))
(setq p7 (list (* (+ 4 0) scale) (* 0 scale)))
(command "PLINE" p1 p2 p3 p4 p5 p6 p7 "")
(setq e2 (entlast))
(setq p1 (list (* (+ 4 1) scale) (* 3 scale)))
(setq p2 (list (* (+ 4 1) scale) (* 4 scale)))
(setq p3 (list (* (+ 4 2) scale) (* 4 scale)))
(setq p4 (list (* (+ 4 2) scale) (* 3 scale)))
(setq p5 (list (* (+ 4 1) scale) (* 3 scale)))
(command "PLINE" p1 p2 p3 p4 p5 "")
(setq _e2 (entlast))
(command "EXTRUDE" e2 "" extrude_scale)
(setq e2_ (entlast))
(command "EXTRUDE" _e2 "" extrude_scale)
(setq __e2 (entlast))
(command "_subtract" e2_ "" __e2 "")

;'О'
(setq p1 (list (* (+ 8 0) scale) (* 0 scale)))
(setq p2 (list (* (+ 8 0) scale) (* 5 scale)))
(setq p3 (list (* (+ 8 3) scale) (* 5 scale)))
(setq p4 (list (* (+ 8 3) scale) (* 0 scale)))
(setq p5 (list (* (+ 8 0) scale) (* 0 scale)))
(command "PLINE" p1 p2 p3 p4 p5 "")
(setq e3 (entlast))
(setq p1 (list (* (+ 8 1) scale) (* 1 scale)))
(setq p2 (list (* (+ 8 1) scale) (* 4 scale)))
(setq p3 (list (* (+ 8 2) scale) (* 4 scale)))
(setq p4 (list (* (+ 8 2) scale) (* 1 scale)))
(setq p5 (list (* (+ 8 1) scale) (* 1 scale)))
(command "PLINE" p1 p2 p3 p4 p5 "")
(setq _e3 (entlast))
(command "EXTRUDE" e3 "" extrude_scale)
(setq e3_ (entlast))
(command "EXTRUDE" _e3 "" extrude_scale)
(setq __e3 (entlast))
(command "_subtract" e3_ "" __e3 "")

;'Г'
(setq p1 (list (* (+ 12 0) scale) (* 0 scale)))
(setq p2 (list (* (+ 12 0) scale) (* 5 scale)))
(setq p3 (list (* (+ 12 3) scale) (* 5 scale)))
(setq p4 (list (* (+ 12 3) scale) (* 3 scale)))
(setq p5 (list (* (+ 12 2) scale) (* 3 scale)))
(setq p6 (list (* (+ 12 2) scale) (* 4 scale)))
(setq p7 (list (* (+ 12 1) scale) (* 4 scale)))
(setq p8 (list (* (+ 12 1) scale) (* 0 scale)))
(setq p9 (list (* (+ 12 0) scale) (* 0 scale)))
(command "PLINE" p1 p2 p3 p4 p5 p6 p7 p8 p9 "")
(command "EXTRUDE" (entlast) "" extrude_scale)

;'У'
(setq p1 (list (* (+ 16 0) scale) (* 0 scale)))
(setq p2 (list (* (+ 16 0) scale) (* 1 scale)))
(setq p3 (list (* (+ 16 2) scale) (* 1 scale)))
(setq p4 (list (* (+ 16 2) scale) (* 2 scale)))
(setq p5 (list (* (+ 16 0) scale) (* 2 scale)))
(setq p6 (list (* (+ 16 0) scale) (* 5 scale)))
(setq p7 (list (* (+ 16 1) scale) (* 5 scale)))
(setq p8 (list (* (+ 16 1) scale) (* 3 scale)))
(setq p9 (list (* (+ 16 2) scale) (* 3 scale)))
(setq p10 (list (* (+ 16 2) scale) (* 5 scale)))
(setq p11 (list (* (+ 16 3) scale) (* 5 scale)))
(setq p12 (list (* (+ 16 3) scale) (* 0 scale)))
(setq p13 (list (* (+ 16 0) scale) (* 0 scale)))
(command "PLINE" p1 p2 p3 p4 p5 p6 p7 p8 p9 p10 p11 p12 p13 "")
(command "EXTRUDE" (entlast) "" extrude_scale)

;'Л'
(setq p1 (list (* (+ 20 0) scale) (* 0 scale)))
(setq p2 (list (* (+ 20 1.5) scale) (* 5 scale)))
(setq p3 (list (* (+ 20 3) scale) (* 0 scale)))
(setq p4 (list (* (+ 20 2) scale) (* 0 scale)))
(setq p5 (list (* (+ 20 1.5) scale) (* 2 scale)))
(setq p6 (list (* (+ 20 1) scale) (* 0 scale)))
(setq p7 (list (* (+ 20 0) scale) (* 0 scale)))
(command "PLINE" p1 p2 p3 p4 p5 p6 p7 "")
(command "EXTRUDE" (entlast) "" extrude_scale)

;'И'
(setq p1 (list (* (+ 24 0) scale) (* 0 scale)))
(setq p2 (list (* (+ 24 0) scale) (* 5 scale)))
(setq p3 (list (* (+ 24 1) scale) (* 5 scale)))
(setq p4 (list (* (+ 24 1) scale) (* 2 scale)))
(setq p5 (list (* (+ 24 2) scale) (* 5 scale)))
(setq p6 (list (* (+ 24 3) scale) (* 5 scale)))
(setq p7 (list (* (+ 24 3) scale) (* 0 scale)))
(setq p8 (list (* (+ 24 2) scale) (* 0 scale)))
(setq p9 (list (* (+ 24 2) scale) (* 3 scale)))
(setq p10 (list (* (+ 24 1) scale) (* 0 scale)))
(setq p11 (list (* (+ 24 0) scale) (* 0 scale)))
(command "PLINE" p1 p2 p3 p4 p5 p6 p7 p8 p9 p10 p11 "")
(command "EXTRUDE" (entlast) "" extrude_scale)

;'В'
(setq p1 (list (* (+ 28 0) scale) (* 0 scale)))
(setq p2 (list (* (+ 28 0) scale) (* 5 scale)))
(setq p3 (list (* (+ 28 2.5) scale) (* 5 scale)))
(setq p4 (list (* (+ 28 2.5) scale) (* 3 scale)))
(setq p5 (list (* (+ 28 3) scale) (* 3 scale)))
(setq p6 (list (* (+ 28 3) scale) (* 0 scale)))
(setq p7 (list (* (+ 28 0) scale) (* 0 scale)))
(command "PLINE" p1 p2 p3 p4 p5 p6 p7 "")
(setq e8 (entlast))
(setq p1 (list (* (+ 28 1) scale) (* 1 scale)))
(setq p2 (list (* (+ 28 1) scale) (* 2 scale)))
(setq p3 (list (* (+ 28 2) scale) (* 2 scale)))
(setq p4 (list (* (+ 28 2) scale) (* 1 scale)))
(setq p5 (list (* (+ 28 1) scale) (* 1 scale)))
(command "PLINE" p1 p2 p3 p4 p5 "")
(command "EXTRUDE" (entlast) "" extrude_scale)
(setq _e8 (entlast))
(setq p1 (list (* (+ 28 1) scale) (* 3 scale)))
(setq p2 (list (* (+ 28 1) scale) (* 4 scale)))
(setq p3 (list (* (+ 28 2) scale) (* 4 scale)))
(setq p4 (list (* (+ 28 2) scale) (* 3 scale)))
(setq p5 (list (* (+ 28 1) scale) (* 3 scale)))
(command "PLINE" p1 p2 p3 p4 p5 "")
(command "EXTRUDE" (entlast) "" extrude_scale)
(setq __e8 (entlast))
(command "EXTRUDE" e8 "" extrude_scale)
(setq e8_ (entlast))
(command "_subtract" e8_ "" _e8 "")
(setq e8_tmp (entlast))
(command "_subtract" e8_tmp "" __e8 "")

;'А'
(setq p1 (list (* (+ 32 0) scale) (* 0 scale)))
(setq p2 (list (* (+ 32 1.5) scale) (* 5 scale)))
(setq p3 (list (* (+ 32 3) scale) (* 0 scale)))
(setq p4 (list (* (+ 32 2) scale) (* 0 scale)))
(setq p5 (list (* (+ 32 1.5) scale) (* 2 scale)))
(setq p6 (list (* (+ 32 1) scale) (* 0 scale)))
(setq p7 (list (* (+ 32 0) scale) (* 0 scale)))
(command "PLINE" p1 p2 p3 p4 p5 p6 p7 "")
(setq e9 (entlast))
(setq p1 (list (* (+ 32 0) scale) (* 1 scale)))
(setq p2 (list (* (+ 32 0) scale) (* 2 scale)))
(setq p3 (list (* (+ 32 3) scale) (* 2 scale)))
(setq p4 (list (* (+ 32 3) scale) (* 1 scale)))
(setq p5 (list (* (+ 32 0) scale) (* 1 scale)))
(command "PLINE" p1 p2 p3 p4 p5 "")
(setq _e9 (entlast))
(command "EXTRUDE" e9 "" extrude_scale)
(setq e9_ (entlast))
(command "EXTRUDE" _e9 "" extrude_scale)
(setq __e9 (entlast))
(command "UNION" e9_ __e9 "")

;'Т'
(setq p1 (list (* (+ 37 0) scale) (* 0 scale)))
(setq p2 (list (* (+ 37 0) scale) (* 4 scale)))
(setq p3 (list (* (+ 37 -1) scale) (* 4 scale)))
(setq p4 (list (* (+ 37 -1) scale) (* 5 scale)))
(setq p5 (list (* (+ 37 2) scale) (* 5 scale)))
(setq p6 (list (* (+ 37 2) scale) (* 4 scale)))
(setq p7 (list (* (+ 37 1) scale) (* 4 scale)))
(setq p8 (list (* (+ 37 1) scale) (* 0 scale)))
(setq p9 (list (* (+ 37 0) scale) (* 0 scale)))
(command "PLINE" p1 p2 p3 p4 p5 p6 p7 p8 p9 "")
(command "EXTRUDE" (entlast) "" extrude_scale)

;'Ь'
(setq p1 (list (* (+ 40 0) scale) (* 0 scale)))
(setq p2 (list (* (+ 40 0) scale) (* 5 scale)))
(setq p3 (list (* (+ 40 1) scale) (* 5 scale)))
(setq p4 (list (* (+ 40 1) scale) (* 3 scale)))
(setq p5 (list (* (+ 40 3) scale) (* 3 scale)))
(setq p6 (list (* (+ 40 3) scale) (* 0 scale)))
(setq p7 (list (* (+ 40 0) scale) (* 0 scale)))
(command "PLINE" p1 p2 p3 p4 p5 p6 p7 "")
(setq e11 (entlast))
(setq p1 (list (* (+ 40 1) scale) (* 1 scale)))
(setq p2 (list (* (+ 40 1) scale) (* 2 scale)))
(setq p3 (list (* (+ 40 2) scale) (* 2 scale)))
(setq p4 (list (* (+ 40 2) scale) (* 1 scale)))
(setq p5 (list (* (+ 40 1) scale) (* 1 scale)))
(command "PLINE" p1 p2 p3 p4 p5 "")
(setq _e11 (entlast))
(command "EXTRUDE" e11 "" extrude_scale)
(setq e11_ (entlast))
(command "EXTRUDE" _e11 "" extrude_scale)
(command "_subtract" e11_ "" (entlast) "")

;'Н'
(setq p1 (list (* (+ 46 0) scale) (* 0 scale)))
(setq p2 (list (* (+ 46 0) scale) (* 5 scale)))
(setq p3 (list (* (+ 46 1) scale) (* 5 scale)))
(setq p4 (list (* (+ 46 1) scale) (* 3 scale)))
(setq p5 (list (* (+ 46 2) scale) (* 3 scale)))
(setq p6 (list (* (+ 46 2) scale) (* 5 scale)))
(setq p7 (list (* (+ 46 3) scale) (* 5 scale)))
(setq p8 (list (* (+ 46 3) scale) (* 0 scale)))
(setq p9 (list (* (+ 46 2) scale) (* 0 scale)))
(setq p10 (list (* (+ 46 2) scale) (* 2 scale)))
(setq p11 (list (* (+ 46 1) scale) (* 2 scale)))
(setq p12 (list (* (+ 46 1) scale) (* 0 scale)))
(setq p13 (list (* (+ 46 0) scale) (* 0 scale)))
(command "PLINE" p1 p2 p3 p4 p5 p6 p7 p8 p9 p10 p11 p12 p13 "")
(command "EXTRUDE" (entlast) "" extrude_scale)

;'Е'
(setq p1 (list (* (+ 50 0) scale) (* 0 scale)))
(setq p2 (list (* (+ 50 0) scale) (* 5 scale)))
(setq p3 (list (* (+ 50 3) scale) (* 5 scale)))
(setq p4 (list (* (+ 50 3) scale) (* 4 scale)))
(setq p5 (list (* (+ 50 1) scale) (* 4 scale)))
(setq p6 (list (* (+ 50 1) scale) (* 3 scale)))
(setq p7 (list (* (+ 50 3) scale) (* 3 scale)))
(setq p8 (list (* (+ 50 3) scale) (* 2 scale)))
(setq p9 (list (* (+ 50 1) scale) (* 2 scale)))
(setq p10 (list (* (+ 50 1) scale) (* 1 scale)))
(setq p11 (list (* (+ 50 3) scale) (* 1 scale)))
(setq p12 (list (* (+ 50 3) scale) (* 0 scale)))
(setq p13 (list (* (+ 50 0) scale) (* 0 scale)))
(command "PLINE" p1 p2 p3 p4 p5 p6 p7 p8 p9 p10 p11 p12 p13 "")
(command "EXTRUDE" (entlast) "" extrude_scale)

;'С'
(setq p1 (list (* (+ 56 0) scale) (* 0 scale)))
(setq p2 (list (* (+ 56 0) scale) (* 5 scale)))
(setq p3 (list (* (+ 56 3) scale) (* 5 scale)))
(setq p4 (list (* (+ 56 3) scale) (* 3 scale)))
(setq p5 (list (* (+ 56 2) scale) (* 3 scale)))
(setq p6 (list (* (+ 56 2) scale) (* 4 scale)))
(setq p7 (list (* (+ 56 1) scale) (* 4 scale)))
(setq p8 (list (* (+ 56 1) scale) (* 1 scale)))
(setq p9 (list (* (+ 56 2) scale) (* 1 scale)))
(setq p10 (list (* (+ 56 2) scale) (* 2 scale)))
(setq p11 (list (* (+ 56 3) scale) (* 2 scale)))
(setq p12 (list (* (+ 56 3) scale) (* 0 scale)))
(setq p13 (list (* (+ 56 0) scale) (* 0 scale)))
(command "PLINE" p1 p2 p3 p4 p5 p6 p7 p8 p9 p10 p11 p12 p13 "")
(command "EXTRUDE" (entlast) "" extrude_scale)

;'Т'
(setq p1 (list (* (+ 61 0) scale) (* 0 scale)))
(setq p2 (list (* (+ 61 0) scale) (* 4 scale)))
(setq p3 (list (* (+ 61 -1) scale) (* 4 scale)))
(setq p4 (list (* (+ 61 -1) scale) (* 5 scale)))
(setq p5 (list (* (+ 61 2) scale) (* 5 scale)))
(setq p6 (list (* (+ 61 2) scale) (* 4 scale)))
(setq p7 (list (* (+ 61 1) scale) (* 4 scale)))
(setq p8 (list (* (+ 61 1) scale) (* 0 scale)))
(setq p9 (list (* (+ 61 0) scale) (* 0 scale)))
(command "PLINE" p1 p2 p3 p4 p5 p6 p7 p8 p9 "")
(command "EXTRUDE" (entlast) "" extrude_scale)

;'И'
(setq p1 (list (* (+ 64 0) scale) (* 0 scale)))
(setq p2 (list (* (+ 64 0) scale) (* 5 scale)))
(setq p3 (list (* (+ 64 1) scale) (* 5 scale)))
(setq p4 (list (* (+ 64 1) scale) (* 2 scale)))
(setq p5 (list (* (+ 64 2) scale) (* 5 scale)))
(setq p6 (list (* (+ 64 3) scale) (* 5 scale)))
(setq p7 (list (* (+ 64 3) scale) (* 0 scale)))
(setq p8 (list (* (+ 64 2) scale) (* 0 scale)))
(setq p9 (list (* (+ 64 2) scale) (* 3 scale)))
(setq p10 (list (* (+ 64 1) scale) (* 0 scale)))
(setq p11 (list (* (+ 64 0) scale) (* 0 scale)))
(command "PLINE" p1 p2 p3 p4 p5 p6 p7 p8 p9 p10 p11 "")
(command "EXTRUDE" (entlast) "" extrude_scale)

;'Л'
(setq p1 (list (* (+ 68 0) scale) (* 0 scale)))
(setq p2 (list (* (+ 68 1.5) scale) (* 5 scale)))
(setq p3 (list (* (+ 68 3) scale) (* 0 scale)))
(setq p4 (list (* (+ 68 2) scale) (* 0 scale)))
(setq p5 (list (* (+ 68 1.5) scale) (* 2 scale)))
(setq p6 (list (* (+ 68 1) scale) (* 0 scale)))
(setq p7 (list (* (+ 68 0) scale) (* 0 scale)))
(command "PLINE" p1 p2 p3 p4 p5 p6 p7 "")
(command "EXTRUDE" (entlast) "" extrude_scale)

;'Ь'
(setq p1 (list (* (+ 72 0) scale) (* 0 scale)))
(setq p2 (list (* (+ 72 0) scale) (* 5 scale)))
(setq p3 (list (* (+ 72 1) scale) (* 5 scale)))
(setq p4 (list (* (+ 72 1) scale) (* 3 scale)))
(setq p5 (list (* (+ 72 3) scale) (* 3 scale)))
(setq p6 (list (* (+ 72 3) scale) (* 0 scale)))
(setq p7 (list (* (+ 72 0) scale) (* 0 scale)))
(command "PLINE" p1 p2 p3 p4 p5 p6 p7 "")
(setq e18 (entlast))
(setq p1 (list (* (+ 72 1) scale) (* 1 scale)))
(setq p2 (list (* (+ 72 1) scale) (* 2 scale)))
(setq p3 (list (* (+ 72 2) scale) (* 2 scale)))
(setq p4 (list (* (+ 72 2) scale) (* 1 scale)))
(setq p5 (list (* (+ 72 1) scale) (* 1 scale)))
(command "PLINE" p1 p2 p3 p4 p5 "")
(setq _e18 (entlast))
(command "EXTRUDE" e18 "" extrude_scale)
(setq e18_ (entlast))
(command "EXTRUDE" _e18 "" extrude_scale)
(command "_subtract" e18_ "" (entlast) "")

;'Н'
(setq p1 (list (* (+ 76 0) scale) (* 0 scale)))
(setq p2 (list (* (+ 76 0) scale) (* 5 scale)))
(setq p3 (list (* (+ 76 1) scale) (* 5 scale)))
(setq p4 (list (* (+ 76 1) scale) (* 3 scale)))
(setq p5 (list (* (+ 76 2) scale) (* 3 scale)))
(setq p6 (list (* (+ 76 2) scale) (* 5 scale)))
(setq p7 (list (* (+ 76 3) scale) (* 5 scale)))
(setq p8 (list (* (+ 76 3) scale) (* 0 scale)))
(setq p9 (list (* (+ 76 2) scale) (* 0 scale)))
(setq p10 (list (* (+ 76 2) scale) (* 2 scale)))
(setq p11 (list (* (+ 76 1) scale) (* 2 scale)))
(setq p12 (list (* (+ 76 1) scale) (* 0 scale)))
(setq p13 (list (* (+ 76 0) scale) (* 0 scale)))
(command "PLINE" p1 p2 p3 p4 p5 p6 p7 p8 p9 p10 p11 p12 p13 "")
(command "EXTRUDE" (entlast) "" extrude_scale)

;'О'
(setq p1 (list (* (+ 80 0) scale) (* 0 scale)))
(setq p2 (list (* (+ 80 0) scale) (* 5 scale)))
(setq p3 (list (* (+ 80 3) scale) (* 5 scale)))
(setq p4 (list (* (+ 80 3) scale) (* 0 scale)))
(setq p5 (list (* (+ 80 0) scale) (* 0 scale)))
(command "PLINE" p1 p2 p3 p4 p5 "")
(setq e20 (entlast))
(setq p1 (list (* (+ 80 1) scale) (* 1 scale)))
(setq p2 (list (* (+ 80 1) scale) (* 4 scale)))
(setq p3 (list (* (+ 80 2) scale) (* 4 scale)))
(setq p4 (list (* (+ 80 2) scale) (* 1 scale)))
(setq p5 (list (* (+ 80 1) scale) (* 1 scale)))
(command "PLINE" p1 p2 p3 p4 p5 "")
(setq _e20 (entlast))
(command "EXTRUDE" e20 "" extrude_scale)
(setq e20_ (entlast))
(command "EXTRUDE" _e20 "" extrude_scale)
(setq __e20 (entlast))
(command "_subtract" e20_ "" __e20 "")

;'!'
(setq p1 (list (* (+ 84 0) scale) (* 0 scale)))
(setq p2 (list (* (+ 84 0) scale) (* 2 scale)))
(setq p3 (list (* (+ 84 2) scale) (* 2 scale)))
(setq p4 (list (* (+ 84 2) scale) (* 0 scale)))
(setq p5 (list (* (+ 84 0) scale) (* 0 scale)))
(command "PLINE" p1 p2 p3 p4 p5 "")
(command "EXTRUDE" (entlast) "" extrude_scale)
(setq p1 (list (* (+ 84 0) scale) (* 3 scale)))
(setq p2 (list (* (+ 84 0) scale) (* 8 scale)))
(setq p3 (list (* (+ 84 2) scale) (* 8 scale)))
(setq p4 (list (* (+ 84 2) scale) (* 3 scale)))
(setq p5 (list (* (+ 84 0) scale) (* 3 scale)))
(command "PLINE" p1 p2 p3 p4 p5 "")
(command "EXTRUDE" (entlast) "" extrude_scale)
